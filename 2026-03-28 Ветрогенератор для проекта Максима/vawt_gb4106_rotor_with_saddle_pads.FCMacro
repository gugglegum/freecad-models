# -*- coding: utf-8 -*-
import math
import FreeCAD as App
import Mesh
import Part

DOC_NAME = "VAWT_GB4106_Rotor"

# ============================================================================
# ПАРАМЕТРЫ РОТОРА
# ============================================================================

# ----------------------------------------------------------------------------
# Общая геометрия ротора
# ----------------------------------------------------------------------------
HEIGHT = 298.0            # Полная высота ротора по оси Z, мм
NUM_BLADES = 3            # Количество лопастей

# ----------------------------------------------------------------------------
# Геометрия лопасти
# ----------------------------------------------------------------------------
BLADE_RADIUS = 140.0       # Расстояние от оси ротора до центра сечения лопасти, мм
BLADE_CHORD = 72.0        # Ширина сечения лопасти по локальной хорде, мм
BLADE_CAMBER = 8.5        # Глубина вогнутости лопасти внутрь ("лодочка"), мм
BLADE_THICK = 3.5         # Максимальная толщина лопасти в средней части профиля, мм
BLADE_EDGE_THICK = 2.0    # Толщина лопасти у кромок, мм
TWIST_DEG = -60.0          # Общая закрутка лопасти от низа к верху, градусы

# ----------------------------------------------------------------------------
# Центральная ось, шайбы-ряды и лучи
# ----------------------------------------------------------------------------
SHAFT_DIAMETER = 16.0     # Наружный диаметр центральной алюминиевой трубы, мм
SHAFT_RADIUS = SHAFT_DIAMETER / 2.0  # Радиус центральной оси, мм
SHAFT_HEIGHT = 260.0      # Высота центральной оси, мм

HUB_RADIUS = 16.0         # Радиус центральной части каждой шайбы, мм
HUB_THICK = 10.0           # Толщина каждой шайбы по Z, мм
HUB_BORE_DIAMETER = SHAFT_DIAMETER + 0.4  # Диаметр центрального отверстия в крестовине, мм

ARM_W = 10.0              # Ширина луча, мм
ARM_TO_HUB_OVERLAP = 3.0  # Насколько луч заходит в центральную шайбу, мм
ARM_SOCKET_CLEARANCE = 0.2  # Посадочный зазор между лучом и отдельным седлом с каждой стороны, мм
ARM_TAB_DEPTH = 4.5       # Насколько луч заходит внутрь отдельного седла, мм
ARM_SOCKET_END_GAP = 0.2  # Небольшой зазор на дне паза, чтобы шип не упирался раньше времени, мм
ARM_INSERT_EXTRA_START = 0.6  # Запас, чтобы карман под вставку гарантированно открывался в паз, мм

MOUNT_THICK = 12.0         # Толщина отдельного криволинейного крепления на луче, мм
MOUNT_CONTACT_GAP = 0.0   # Зазор между седлом и ответным креплением (0.0 => без зазора)
MOUNT_HOLE_CLEAR_DIAMETER = 3.5   # Сквозной диаметр под винт M3 в ответном креплении, мм
MOUNT_HOLE_HEAD_DIAMETER = 6.5    # Диаметр расточки под цилиндрическую головку DIN912 M3, мм
MOUNT_HOLE_HEAD_DEPTH = 3.5       # Глубина расточки под головку (со внутренней стороны), мм
MOUNT_HOLE_EXTRA_START = 2.0  # Запас вылета отверстия за внутреннюю поверхность для надежного вскрытия, мм
MOUNT_HOLE_EXTRA_DEPTH = 0.8  # Насколько отверстие проходит дальше контактной поверхности, мм
MOUNT_SOCKET_CLEANUP = 0.6    # Запас старта малого отверстия от дна прямоугольного паза, мм

# ----------------------------------------------------------------------------
# Точность аппроксимации лопасти
# ----------------------------------------------------------------------------
NZ = 50 * 5                   # Количество сечений лопасти по высоте
NX = 60 * 5                   # Количество точек в одном сечении лопасти

# ============================================================================
# ПАРАМЕТРЫ ВНУТРЕННИХ СЁДЕЛ КРЕПЛЕНИЯ
# ============================================================================

# ----------------------------------------------------------------------------
# Расположение рядов седел
# ----------------------------------------------------------------------------
ROW_EDGE_MARGIN = 26.0    # Отступ верхнего и нижнего ряда седел от краёв лопасти, мм
ROW_ZS = [
    -HEIGHT / 2.0 + ROW_EDGE_MARGIN,  # Нижний ряд седел
    0.0,                              # Средний ряд седел
    HEIGHT / 2.0 - ROW_EDGE_MARGIN,   # Верхний ряд седел
]

CHORD_OFFSETS = [-9.0, 9.0]  # Положение двух отверстий в одном седле по хорде лопасти, мм

# ----------------------------------------------------------------------------
# Геометрия седла
# ----------------------------------------------------------------------------
PAD_X_MARGIN = 6.0           # Добавка по ширине седла за пределы крайних отверстий, мм
PAD_HEIGHT = 16.0            # Высота одного седла по Z, мм
PAD_THICK = 7.0              # Максимальная толщина седла от внутренней поверхности лопасти внутрь, мм
PAD_EMBED = 0.35             # Небольшое заглубление седла в mesh-лопасть для гарантированного контакта, мм

# ----------------------------------------------------------------------------
# Нижний и верхний пандус седла
# ----------------------------------------------------------------------------
PAD_BOTTOM_RAMP = 6.0        # Высота нижнего пандуса, мм
PAD_BOTTOM_MIN_THICK = 0.8   # Толщина седла у самого нижнего края, мм

PAD_TOP_RAMP = 6.0           # Высота верхнего пандуса, мм
PAD_TOP_MIN_THICK = 0.8      # Толщина седла у самого верхнего края, мм

# ----------------------------------------------------------------------------
# Точность аппроксимации седла
# ----------------------------------------------------------------------------
PAD_NX = 18                  # Количество точек по ширине одного сечения седла
PAD_NZ = 9                   # Количество сечений седла по высоте

# ----------------------------------------------------------------------------
# Глухие отверстия под латунные вставки / термовставки
# ----------------------------------------------------------------------------
INSERT_HOLE_DIAMETER = 4.35   # Диаметр отверстия под вставку, мм
INSERT_HOLE_DEPTH = 4.5      # Номинальная глубина отверстия, мм
HUB_SET_SCREW_CLEAR_DIAMETER = 3.6  # Сквозное отверстие под установочный винт M3 в шайбе, мм
MIN_CAP_TO_BLADE = 1.0       # Минимальный слой пластика между дном отверстия и стороной седла, прилегающей к лопасти, мм

# Эти два параметра нужны, чтобы булево вычитание надёжно "открывало" отверстие наружу
HOLE_EXTRA_START = 1.40      # Насколько отверстие начинается снаружи от лицевой поверхности седла, мм
HOLE_EXTRA_DEPTH = 1.20      # Насколько отверстие режется глубже номинальной глубины, мм

# ----------------------------------------------------------------------------
# Вспомогательные маркеры центров отверстий
# ----------------------------------------------------------------------------
CREATE_MARKERS = False       # Создавать ли красные шарики-маркеры центров отверстий
MARKER_RADIUS = 1.0          # Радиус красного маркера, мм

# ----------------------------------------------------------------------------
# Префиксы имён объектов
# ----------------------------------------------------------------------------
PAD_PREFIX = "BladeSaddles_"
MARK_PREFIX = "SaddleMarkers_"
HUB_MOUNT_PREFIX = "HubMount_"

BLADE_COLOR = (0.94, 0.94, 0.90)
HUB_ROW_COLOR = (0.22, 0.22, 0.22)
HUB_MOUNT_COLOR = (1.00, 0.38, 0.03)
SHAFT_COLOR = (0.72, 0.75, 0.74)
SHAFT_SPECULAR_COLOR = (0.95, 0.95, 0.92)
SHAFT_SHININESS = 0.80

# ============================================================================
# ВСПОМОГАТЕЛЬНЫЕ ФУНКЦИИ
# ============================================================================

def ensure_doc(name):
    """Возвращает существующий документ по имени или создаёт новый."""
    docs = App.listDocuments()
    if name in docs:
        return docs[name]
    return App.newDocument(name)


def clear_generated_objects(doc):
    """Удаляет ранее созданные макросом объекты."""
    prefixes = (
        "Blade_",
        "Hub_",
        "HubRow_",
        "Arm_",
        "Shaft",
        PAD_PREFIX,
        MARK_PREFIX,
        HUB_MOUNT_PREFIX,
    )

    for obj in list(doc.Objects):
        if obj.Name.startswith(prefixes) or obj.Label.startswith(prefixes):
            try:
                doc.removeObject(obj.Name)
            except Exception:
                pass


def v_add(a, b):
    """Сложение двух 3D-векторов, заданных как кортежи."""
    return (a[0] + b[0], a[1] + b[1], a[2] + b[2])


def v_sub(a, b):
    """Вычитание двух 3D-векторов, заданных как кортежи."""
    return (a[0] - b[0], a[1] - b[1], a[2] - b[2])


def v_scale(v, s):
    """Умножение 3D-вектора на скаляр."""
    return (v[0] * s, v[1] * s, v[2] * s)


def to_vec(v):
    """Преобразование кортежа координат в App.Vector."""
    return App.Vector(v[0], v[1], v[2])


def fuse_shapes(shapes):
    """Склеивает список Part-форм в одну форму."""
    if not shapes:
        raise RuntimeError("No shapes to fuse.")

    try:
        fused = shapes[0].multiFuse(shapes[1:])
    except Exception:
        fused = shapes[0]
        for shp in shapes[1:]:
            fused = fused.fuse(shp)

    try:
        fused = fused.removeSplitter()
    except Exception:
        pass

    return fused


def keep_largest_solid(shape):
    """Оставляет только самое большое твердое тело, отбрасывая мелкие осколки."""
    solids = list(getattr(shape, "Solids", []))
    if not solids:
        return shape

    largest = max(solids, key=lambda solid: solid.Volume)
    return largest.copy()


def cut_counterbored_hole(shape, start_point, axis_dir, clear_diameter, clear_length, head_diameter, head_length):
    """Вычитает из формы двухступенчатое цилиндрическое отверстие."""
    clear_hole = Part.makeCylinder(
        clear_diameter / 2.0,
        clear_length,
        to_vec(start_point),
        to_vec(axis_dir)
    )
    shape = shape.cut(clear_hole)

    if head_length > 0.0:
        head_hole = Part.makeCylinder(
            head_diameter / 2.0,
            head_length,
            to_vec(start_point),
            to_vec(axis_dir)
        )
        shape = shape.cut(head_hole)

    return shape

# ============================================================================
# МАТЕМАТИКА ЛОПАСТИ
# ============================================================================

def blade_section_values(x_local):
    """
    Возвращает:
    - yc: смещение средней линии профиля внутрь
    - yt: локальную толщину профиля
    """
    xc = x_local / (BLADE_CHORD / 2.0)
    xc = max(-1.0, min(1.0, xc))

    yc = BLADE_CAMBER * (1.0 - xc * xc)
    yt = BLADE_EDGE_THICK + (BLADE_THICK - BLADE_EDGE_THICK) * (1.0 - abs(xc) ** 1.5)

    return yc, yt


def blade_frame(phase_deg, z):
    """
    Возвращает локальную систему координат лопасти на высоте z:
    - center: центр сечения
    - tang: направление хорды
    - inward: направление внутрь ротора
    """
    frac = (z + HEIGHT / 2.0) / HEIGHT
    phi = math.radians(phase_deg) + math.radians(TWIST_DEG) * (frac - 0.5)

    tang = (-math.sin(phi), math.cos(phi), 0.0)
    inward = (-math.cos(phi), -math.sin(phi), 0.0)
    center = (BLADE_RADIUS * math.cos(phi), BLADE_RADIUS * math.sin(phi), z)

    return center, tang, inward


def blade_inner_surface_point(phase_deg, z, x_local):
    """
    Точка на внутренней поверхности лопасти в локальной координате x_local и на высоте z.
    """
    center, tang, inward = blade_frame(phase_deg, z)
    yc, yt = blade_section_values(x_local)

    p = v_add(center, v_add(v_scale(tang, x_local), v_scale(inward, yc + yt / 2.0)))
    return p, inward


def blade_loops(phase_deg):
    """
    Создаёт набор замкнутых контуров по высоте, из которых строится mesh лопасти.
    """
    loops = []

    xs = [-BLADE_CHORD / 2.0 + i * (BLADE_CHORD / float(NX - 1)) for i in range(NX)]
    zs = [-HEIGHT / 2.0 + i * (HEIGHT / float(NZ - 1)) for i in range(NZ)]

    for z in zs:
        center, tang, inward = blade_frame(phase_deg, z)
        loop = []

        # Верхняя половина профиля
        for x in xs:
            yc, yt = blade_section_values(x)
            p = v_add(center, v_add(v_scale(tang, x), v_scale(inward, yc + yt / 2.0)))
            loop.append(p)

        # Нижняя половина профиля
        for x in reversed(xs):
            yc, yt = blade_section_values(x)
            p = v_add(center, v_add(v_scale(tang, x), v_scale(inward, yc - yt / 2.0)))
            loop.append(p)

        loops.append(loop)

    return loops


def make_blade_mesh(phase_deg):
    """
    Строит mesh одной лопасти как набор треугольников.
    """
    loops = blade_loops(phase_deg)
    nloop = len(loops[0])
    facets = []

    def vertex(loop_index, point_index):
        return loops[loop_index][point_index % nloop]

    # Боковая поверхность
    for iz in range(len(loops) - 1):
        for j in range(nloop):
            a = vertex(iz, j)
            b = vertex(iz, j + 1)
            c = vertex(iz + 1, j)
            d = vertex(iz + 1, j + 1)

            facets.append((App.Vector(*a), App.Vector(*c), App.Vector(*b)))
            facets.append((App.Vector(*b), App.Vector(*c), App.Vector(*d)))

    # Нижняя крышка
    bot_center = (
        sum(p[0] for p in loops[0]) / nloop,
        sum(p[1] for p in loops[0]) / nloop,
        sum(p[2] for p in loops[0]) / nloop,
    )
    for j in range(nloop):
        a = vertex(0, j)
        b = vertex(0, j + 1)
        facets.append((App.Vector(*bot_center), App.Vector(*b), App.Vector(*a)))

    # Верхняя крышка
    top_center = (
        sum(p[0] for p in loops[-1]) / nloop,
        sum(p[1] for p in loops[-1]) / nloop,
        sum(p[2] for p in loops[-1]) / nloop,
    )
    for j in range(nloop):
        a = vertex(len(loops) - 1, j)
        b = vertex(len(loops) - 1, j + 1)
        facets.append((App.Vector(*top_center), App.Vector(*a), App.Vector(*b)))

    return Mesh.Mesh(facets)

# ============================================================================
# МАТЕМАТИКА СЕДЛА
# ============================================================================

def local_pad_thickness(z_local_from_bottom):
    """
    Возвращает локальную толщину седла на заданной высоте внутри седла.
    Толщина уменьшается у нижнего и верхнего края, образуя пандусы.
    """
    thickness = PAD_THICK

    # Нижний пандус
    if PAD_BOTTOM_RAMP > 0:
        if z_local_from_bottom <= 0:
            thickness = min(thickness, PAD_BOTTOM_MIN_THICK)
        elif z_local_from_bottom < PAD_BOTTOM_RAMP:
            k = z_local_from_bottom / PAD_BOTTOM_RAMP
            bottom_t = PAD_BOTTOM_MIN_THICK + k * (PAD_THICK - PAD_BOTTOM_MIN_THICK)
            thickness = min(thickness, bottom_t)

    # Верхний пандус
    if PAD_TOP_RAMP > 0:
        dist_from_top = PAD_HEIGHT - z_local_from_bottom
        if dist_from_top <= 0:
            thickness = min(thickness, PAD_TOP_MIN_THICK)
        elif dist_from_top < PAD_TOP_RAMP:
            k = dist_from_top / PAD_TOP_RAMP
            top_t = PAD_TOP_MIN_THICK + k * (PAD_THICK - PAD_TOP_MIN_THICK)
            thickness = min(thickness, top_t)

    return thickness


def make_closed_section_wire(phase_deg, z, z_center, x_left, x_right):
    """
    Создаёт одно замкнутое сечение седла на высоте z.
    Внутренняя сторона повторяет кривизну лопасти,
    внешняя сторона смещена внутрь ротора на локальную толщину.
    """
    z0 = z_center - PAD_HEIGHT / 2.0
    t_local = local_pad_thickness(z - z0)

    pts_inner = []
    pts_outer = []

    for i in range(PAD_NX):
        a = float(i) / float(PAD_NX - 1)
        x = x_left + (x_right - x_left) * a

        p, inward = blade_inner_surface_point(phase_deg, z, x)
        p_inner = v_sub(p, v_scale(inward, PAD_EMBED))
        p_outer = v_add(p_inner, v_scale(inward, t_local))

        pts_inner.append(to_vec(p_inner))
        pts_outer.append(to_vec(p_outer))

    poly = []
    poly.extend(pts_inner)
    poly.extend(reversed(pts_outer))
    poly.append(pts_inner[0])

    return Part.makePolygon(poly)


def make_saddle_solid(phase_deg, z_center):
    """
    Создаёт одно седло как loft из нескольких сечений,
    а затем вычитает два глухих отверстия.
    """
    x_left = min(CHORD_OFFSETS) - PAD_X_MARGIN
    x_right = max(CHORD_OFFSETS) + PAD_X_MARGIN

    if INSERT_HOLE_DEPTH > PAD_THICK - MIN_CAP_TO_BLADE:
        raise RuntimeError(
            "INSERT_HOLE_DEPTH слишком велик для текущего PAD_THICK. "
            "Увеличьте PAD_THICK или уменьшите INSERT_HOLE_DEPTH."
        )

    z0 = z_center - PAD_HEIGHT / 2.0
    z1 = z_center + PAD_HEIGHT / 2.0

    wires = []
    for iz in range(PAD_NZ):
        tz = float(iz) / float(PAD_NZ - 1)
        z = z0 + (z1 - z0) * tz
        wires.append(make_closed_section_wire(phase_deg, z, z_center, x_left, x_right))

    shape = Part.makeLoft(wires, True, False)

    # Два глухих отверстия
    for x_local in CHORD_OFFSETS:
        p, inward = blade_inner_surface_point(phase_deg, z_center, x_local)
        p_inner = v_sub(p, v_scale(inward, PAD_EMBED))
        face_point = v_add(p_inner, v_scale(inward, PAD_THICK))

        hole_start = v_add(face_point, v_scale(inward, HOLE_EXTRA_START))
        hole_dir = to_vec(v_scale(inward, -1.0))

        hole = Part.makeCylinder(
            INSERT_HOLE_DIAMETER / 2.0,
            INSERT_HOLE_DEPTH + HOLE_EXTRA_START + HOLE_EXTRA_DEPTH,
            to_vec(hole_start),
            hole_dir
        )

        shape = shape.cut(hole)

    return shape


def make_marker_shape(phase_deg, z_center):
    """
    Создаёт два красных шарика-маркера центров отверстий.
    Полезно только для отладки.
    """
    markers = []

    for x_local in CHORD_OFFSETS:
        p, inward = blade_inner_surface_point(phase_deg, z_center, x_local)
        p_inner = v_sub(p, v_scale(inward, PAD_EMBED))
        p_face = v_add(p_inner, v_scale(inward, PAD_THICK))

        markers.append(Part.makeSphere(MARKER_RADIUS, to_vec(p_face)))

    return Part.makeCompound(markers)

# ============================================================================
# ГЕНЕРАЦИЯ ШАЙБ С ЛУЧАМИ И ОТДЕЛЬНЫМИ СЕДЛОВИДНЫМИ КРЕПЛЕНИЯМИ
# ============================================================================

def saddle_face_point(phase_deg, z, z_center, x_local):
    """
    Точка на внешней стороне седла на лопасти (со стороны центра ротора) на высоте z.
    """
    z0 = z_center - PAD_HEIGHT / 2.0
    t_local = local_pad_thickness(z - z0)

    p, inward = blade_inner_surface_point(phase_deg, z, x_local)
    p_inner = v_sub(p, v_scale(inward, PAD_EMBED))
    p_face = v_add(p_inner, v_scale(inward, t_local))

    return p_face, inward


def mount_center_frame(phase_deg, z_center):
    """
    Возвращает локальную рамку центральной точки отдельного седловидного крепления.
    """
    x_mid = 0.5 * (min(CHORD_OFFSETS) + max(CHORD_OFFSETS))
    p_face, inward = saddle_face_point(phase_deg, z_center, z_center, x_mid)
    p_contact = v_add(p_face, v_scale(inward, MOUNT_CONTACT_GAP))
    p_mount_inner = v_add(p_contact, v_scale(inward, MOUNT_THICK))
    outward = v_scale(inward, -1.0)

    angle_inward_deg = math.degrees(math.atan2(inward[1], inward[0]))
    angle_outward_deg = math.degrees(math.atan2(outward[1], outward[0]))

    return p_contact, p_mount_inner, inward, outward, angle_inward_deg, angle_outward_deg


def arm_socket_dimensions():
    """
    Размеры прямоугольного паза в отдельном седле под профиль луча.
    """
    socket_width = ARM_W + 2.0 * ARM_SOCKET_CLEARANCE
    socket_height = HUB_THICK + 2.0 * ARM_SOCKET_CLEARANCE

    return socket_width, socket_height


def make_mount_section_wire(phase_deg, z, z_center, x_left, x_right):
    """
    Замкнутое сечение отдельного седловидного крепления.
    Внутренняя сторона повторяет внешнюю сторону седла на лопасти.
    """
    pts_contact = []
    pts_outer = []

    for i in range(PAD_NX):
        a = float(i) / float(PAD_NX - 1)
        x = x_left + (x_right - x_left) * a

        p_face, inward = saddle_face_point(phase_deg, z, z_center, x)
        p_contact = v_add(p_face, v_scale(inward, MOUNT_CONTACT_GAP))
        p_outer = v_add(p_contact, v_scale(inward, MOUNT_THICK))

        pts_contact.append(to_vec(p_contact))
        pts_outer.append(to_vec(p_outer))

    poly = []
    poly.extend(pts_contact)
    poly.extend(reversed(pts_outer))
    poly.append(pts_contact[0])

    return Part.makePolygon(poly)


def make_mount_solid(phase_deg, z_center):
    """
    Отдельное седловидное крепление:
    - криволинейная часть, которая прилегает к седлу на лопасти
    - два боковых отверстия под винты к лопасти
    - прямоугольный паз под луч
    - центральное отверстие под винт к лучу
    """
    x_left = min(CHORD_OFFSETS) - PAD_X_MARGIN
    x_right = max(CHORD_OFFSETS) + PAD_X_MARGIN

    z0 = z_center - PAD_HEIGHT / 2.0
    z1 = z_center + PAD_HEIGHT / 2.0

    wires = []
    for iz in range(PAD_NZ):
        tz = float(iz) / float(PAD_NZ - 1)
        z = z0 + (z1 - z0) * tz
        wires.append(make_mount_section_wire(phase_deg, z, z_center, x_left, x_right))

    shape = Part.makeLoft(wires, True, False)

    _, p_mount_inner, inward, outward, angle_inward_deg, angle_outward_deg = mount_center_frame(phase_deg, z_center)
    socket_width, socket_height = arm_socket_dimensions()
    socket_depth = ARM_TAB_DEPTH + ARM_SOCKET_END_GAP
    remaining_material = MOUNT_THICK - socket_depth

    if remaining_material <= 0.0:
        raise RuntimeError(
            "ARM_TAB_DEPTH слишком велик для текущего MOUNT_THICK. "
            "Увеличьте MOUNT_THICK или уменьшите ARM_TAB_DEPTH."
        )
    if remaining_material < MOUNT_HOLE_HEAD_DEPTH:
        raise RuntimeError(
            "Для скрытой головки DIN912 M3 не хватает толщины. "
            "Увеличьте MOUNT_THICK или уменьшите ARM_TAB_DEPTH / MOUNT_HOLE_HEAD_DEPTH."
        )

    # Прямоугольный паз в седле, в который входит сам луч.
    socket = Part.makeBox(socket_depth, socket_width, socket_height)
    socket.translate(App.Vector(-socket_depth, -socket_width / 2.0, z_center - socket_height / 2.0))
    socket.rotate(App.Vector(0, 0, 0), App.Vector(0, 0, 1), angle_inward_deg)
    socket.translate(App.Vector(p_mount_inner[0], p_mount_inner[1], 0))

    side_head_depth = max(0.0, min(MOUNT_HOLE_HEAD_DEPTH, MOUNT_THICK))
    side_clear_length = MOUNT_THICK + MOUNT_HOLE_EXTRA_START + MOUNT_HOLE_EXTRA_DEPTH
    side_head_length = side_head_depth + MOUNT_HOLE_EXTRA_START

    # Два отверстия под винты, которые крепят отдельное седло к седлу на лопасти.
    for x_local in CHORD_OFFSETS:
        p_face, inward = saddle_face_point(phase_deg, z_center, z_center, x_local)
        p_contact = v_add(p_face, v_scale(inward, MOUNT_CONTACT_GAP))
        hole_start = v_add(p_contact, v_scale(inward, MOUNT_THICK + MOUNT_HOLE_EXTRA_START))

        shape = cut_counterbored_hole(
            shape,
            hole_start,
            v_scale(inward, -1.0),
            MOUNT_HOLE_CLEAR_DIAMETER,
            side_clear_length,
            MOUNT_HOLE_HEAD_DIAMETER,
            side_head_length
        )

    # Центральный винт тянет луч к седлу.
    # Малое отверстие 3.5 мм должно выходить именно в дно паза, а расточка
    # под головку 6.5 мм должна оставаться только на противоположной стороне.
    center_face, inward = saddle_face_point(phase_deg, z_center, z_center, 0.0)
    center_contact = v_add(center_face, v_scale(inward, MOUNT_CONTACT_GAP))
    socket_bottom = v_sub(p_mount_inner, v_scale(inward, socket_depth))

    clear_start = v_add(socket_bottom, v_scale(inward, MOUNT_SOCKET_CLEANUP))
    clear_hole = Part.makeCylinder(
        MOUNT_HOLE_CLEAR_DIAMETER / 2.0,
        remaining_material + MOUNT_SOCKET_CLEANUP + MOUNT_HOLE_EXTRA_DEPTH,
        to_vec(clear_start),
        to_vec(v_scale(inward, -1.0))
    )

    head_start = v_sub(center_contact, v_scale(inward, MOUNT_HOLE_EXTRA_START))
    head_hole = Part.makeCylinder(
        MOUNT_HOLE_HEAD_DIAMETER / 2.0,
        MOUNT_HOLE_HEAD_DEPTH + MOUNT_HOLE_EXTRA_START,
        to_vec(head_start),
        to_vec(inward)
    )

    # Центральную зону режем одним общим инструментом, чтобы на плоскости паза
    # не оставались артефакты от нескольких пересекающихся булевых операций.
    center_cutter = fuse_shapes([socket, clear_hole, head_hole])
    shape = shape.cut(center_cutter)
    shape = keep_largest_solid(shape)

    try:
        shape = shape.removeSplitter()
    except Exception:
        pass

    shape = keep_largest_solid(shape)

    return shape


def make_arm_shape(phase_deg, z_center):
    """
    Прямой луч от центральной шайбы до отдельного седловидного крепления.
    Конец луча входит в прямоугольный паз отдельного седла.
    На торце луча создаётся карман под латунную вставку.
    """
    _, p_mount_inner, inward, outward, _, angle_outward_deg = mount_center_frame(phase_deg, z_center)
    arm_tip_point = v_sub(p_mount_inner, v_scale(inward, ARM_TAB_DEPTH))
    arm_end_radius = math.hypot(arm_tip_point[0], arm_tip_point[1])
    arm_start_radius = max(0.0, HUB_RADIUS - ARM_TO_HUB_OVERLAP)
    arm_len = max(1.0, arm_end_radius - arm_start_radius)

    arm = Part.makeBox(arm_len, ARM_W, HUB_THICK)
    arm.translate(App.Vector(arm_start_radius, -ARM_W / 2.0, z_center - HUB_THICK / 2.0))
    arm.rotate(App.Vector(0, 0, 0), App.Vector(0, 0, 1), angle_outward_deg)

    # Карман под латунную вставку режется с торца луча вдоль его оси.
    insert_start = v_add(arm_tip_point, v_scale(outward, ARM_INSERT_EXTRA_START))
    insert_hole = Part.makeCylinder(
        INSERT_HOLE_DIAMETER / 2.0,
        INSERT_HOLE_DEPTH + ARM_INSERT_EXTRA_START,
        to_vec(insert_start),
        to_vec(inward)
    )
    arm = arm.cut(insert_hole)

    try:
        arm = arm.removeSplitter()
    except Exception:
        pass

    return arm


def make_hub_row_shape(z_center):
    """
    Создаёт одну крестовину: центральную шайбу и три луча без криволинейных седел.
    """
    shapes = []
    hub = Part.makeCylinder(
        HUB_RADIUS,
        HUB_THICK,
        App.Vector(0, 0, z_center - HUB_THICK / 2.0),
        App.Vector(0, 0, 1)
    )
    shapes.append(hub)

    for blade_index in range(NUM_BLADES):
        phase = blade_index * (360.0 / NUM_BLADES)
        shapes.append(make_arm_shape(phase, z_center))

    shape = fuse_shapes(shapes)
    hub_bore = Part.makeCylinder(
        HUB_BORE_DIAMETER / 2.0,
        SHAFT_HEIGHT,
        App.Vector(0, 0, -SHAFT_HEIGHT / 2.0),
        App.Vector(0, 0, 1)
    )
    shape = shape.cut(hub_bore)

    hole_angle_step = 360.0 / NUM_BLADES
    _, _, _, _, _, base_arm_angle_deg = mount_center_frame(0.0, z_center)
    hole_start_radius = HUB_BORE_DIAMETER / 2.0 - HOLE_EXTRA_START
    clear_hole_length = HUB_RADIUS - hole_start_radius + HOLE_EXTRA_DEPTH

    for hole_index in range(NUM_BLADES):
        angle = math.radians(base_arm_angle_deg + (hole_index + 0.5) * hole_angle_step)
        radial = (math.cos(angle), math.sin(angle), 0.0)
        start = v_scale(radial, hole_start_radius)
        start = (start[0], start[1], z_center)

        insert_hole = Part.makeCylinder(
            INSERT_HOLE_DIAMETER / 2.0,
            INSERT_HOLE_DEPTH + HOLE_EXTRA_START,
            to_vec(start),
            to_vec(radial)
        )
        clear_hole = Part.makeCylinder(
            HUB_SET_SCREW_CLEAR_DIAMETER / 2.0,
            clear_hole_length,
            to_vec(start),
            to_vec(radial)
        )
        shape = shape.cut(fuse_shapes([insert_hole, clear_hole]))

    try:
        shape = shape.removeSplitter()
    except Exception:
        pass

    return keep_largest_solid(shape)


def build_hub_rows(doc):
    """
    Создаёт три крестовины по позициям ROW_ZS.
    """
    created = 0

    for row_index, z_center in enumerate(ROW_ZS, start=1):
        obj = doc.addObject("Part::Feature", "HubRow_%d" % row_index)
        obj.Shape = make_hub_row_shape(z_center)
        try:
            obj.ViewObject.ShapeColor = HUB_ROW_COLOR
        except Exception:
            pass
        created += 1

    return created


def build_hub_mounts(doc):
    """
    Создаёт отдельные седловидные крепления для каждой крестовины.
    """
    created = 0

    for row_index, z_center in enumerate(ROW_ZS, start=1):
        for blade_index in range(NUM_BLADES):
            phase = blade_index * (360.0 / NUM_BLADES)
            obj = doc.addObject("Part::Feature", "%s%d_%d" % (HUB_MOUNT_PREFIX, row_index, blade_index + 1))
            obj.Shape = make_mount_solid(phase, z_center)
            try:
                obj.ViewObject.ShapeColor = HUB_MOUNT_COLOR
            except Exception:
                pass
            created += 1

    return created

# ============================================================================
# ГЕНЕРАЦИЯ РОТОРА
# ============================================================================

def build_rotor(doc):
    """Создаёт лопасти и центральную ось."""
    # Лопасти
    for i in range(NUM_BLADES):
        phase = i * (360.0 / NUM_BLADES)
        mesh = make_blade_mesh(phase)

        obj = doc.addObject("Mesh::Feature", "Blade_%d" % (i + 1))
        obj.Mesh = mesh
        try:
            obj.ViewObject.ShapeColor = BLADE_COLOR
        except Exception:
            pass

    # Центральная ось
    shaft = doc.addObject("Part::Cylinder", "Shaft")
    shaft.Radius = SHAFT_RADIUS
    shaft.Height = SHAFT_HEIGHT
    shaft.Placement.Base = App.Vector(0, 0, -SHAFT_HEIGHT / 2.0)
    try:
        shaft.ViewObject.ShapeColor = SHAFT_COLOR
        mat = shaft.ViewObject.ShapeAppearance[0]
        mat.DiffuseColor = (SHAFT_COLOR[0], SHAFT_COLOR[1], SHAFT_COLOR[2], 1.0)
        mat.AmbientColor = (0.35, 0.36, 0.36, 1.0)
        mat.SpecularColor = (SHAFT_SPECULAR_COLOR[0], SHAFT_SPECULAR_COLOR[1], SHAFT_SPECULAR_COLOR[2], 1.0)
        mat.Shininess = SHAFT_SHININESS
        shaft.ViewObject.ShapeAppearance = (mat,)
    except Exception:
        pass

# ============================================================================
# ГЕНЕРАЦИЯ СЁДЕЛ
# ============================================================================

def build_saddles(doc):
    """Создаёт седла крепления на каждой лопасти."""
    created = 0

    for blade_index in range(NUM_BLADES):
        phase = blade_index * (360.0 / NUM_BLADES)

        pad_shapes = []
        marker_shapes = []

        for zc in ROW_ZS:
            pad_shapes.append(make_saddle_solid(phase, zc))
            created += 1

            if CREATE_MARKERS:
                marker_shapes.append(make_marker_shape(phase, zc))

        pad_obj = doc.addObject("Part::Feature", PAD_PREFIX + str(blade_index + 1))
        pad_obj.Shape = Part.makeCompound(pad_shapes)
        try:
            pad_obj.ViewObject.ShapeColor = BLADE_COLOR
        except Exception:
            pass

        if CREATE_MARKERS:
            mark_obj = doc.addObject("Part::Feature", MARK_PREFIX + str(blade_index + 1))
            mark_obj.Shape = Part.makeCompound(marker_shapes)
            try:
                mark_obj.ViewObject.ShapeColor = (0.90, 0.10, 0.10)
            except Exception:
                pass

    return created

# ============================================================================
# ОСНОВНОЙ ЗАПУСК
# ============================================================================

doc = ensure_doc(DOC_NAME)
App.setActiveDocument(doc.Name)

clear_generated_objects(doc)

build_rotor(doc)
created_saddles = build_saddles(doc)
created_hub_rows = build_hub_rows(doc)
created_hub_mounts = build_hub_mounts(doc)

doc.recompute()

try:
    import FreeCADGui as Gui
    Gui.ActiveDocument.ActiveView.fitAll()
except Exception:
    pass

print("VAWT rotor created successfully.")
print("Created %d saddle pads." % created_saddles)
print("Created %d hub rows." % created_hub_rows)
print("Created %d detachable hub mounts." % created_hub_mounts)
